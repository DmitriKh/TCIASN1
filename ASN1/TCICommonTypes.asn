TCI-CommonTypes
DEFINITIONS AUTOMATIC TAGS ::= 
BEGIN

IMPORTS
VarLengthNumber FROM CITSapplMgmtIDs {iso(1) standard(0) cits-applMgmt (17419) ids (1) version1 (1)} -- this is the p-encoded PSID
;

PduData ::= Opaque
PduType ::= ENUMERATED {
    d80211frame         (1),    -- 802.11 frame (802.11 header, MAC header) // DEPRECATED. Use d16093payload instead
    d16093frame         (2),    -- WSM frame, including WSM header & payload  // DEPRECATED. Use d16093payload instead
    d16092data          (3),    -- Ieee1609Data including 1609.3 payload
    d16093payload       (4),    -- 1609.3 payload excluding security header/footer
    dIpv6payload        (5)     -- Ipv6 payload
}

Opaque ::= OCTET STRING(SIZE(0..2304)) -- mtu_size 1500 for Ethernet
HashedId8  ::= OCTET STRING (SIZE(8))

/* 
   Response Messages with simple Result
*/ 

Response ::= SEQUENCE {
    msgID               MsgID,
    resultCode          ResultCode,
    exception           Exception OPTIONAL,
    ...
}

ResultCode ::= ENUMERATED {
    rcSuccess (0), -- success
    rcFailure (1)  -- failure
}

/* 
    Exception Messages 
*/
Exception ::= SEQUENCE{
    type        ExceptionType,
    id          ExceptionId OPTIONAL,
    module      Module OPTIONAL,    
    description ExceptionText OPTIONAL,
    ...
}

ExceptionType   ::= ENUMERATED{
    info        (0), -- all info messages
    warning     (1), -- all warnings
    error       (2)  -- all errors
}

Module ::= UTF8String (SIZE(0..255))
-- Function/Module reporting an exception

ExceptionId ::= ENUMERATED {
 critical-error (1),
 incorrect-parameter-value (2),
 missing-parameter (3),
 radio-interface-unavailable (4),
 ...    -- future exception IDs
}

ExceptionText ::= UTF8String (SIZE(0..1200))
-- short description of exception

RadioInterface ::= SEQUENCE{
    radio       Radio,
    antenna     Antenna OPTIONAL
}

Radio ::= ENUMERATED {
    radio0 (0),
    radio1 (1),
    radio2 (2),
    radio3 (3)
}

Antenna ::= ENUMERATED {
    antenna1    (1),
    antenna2    (2),
    both        (3)
}

TimeSlot ::= ENUMERATED {    -- consistent with dot3
    alt-slot0       (1),
    alt-slot1       (2),
    continuous      (3)
}

RCPI ::= INTEGER (0..255)
UserPriority ::= INTEGER(0..7)
Time64 ::= INTEGER (0..9223372036854775807) 
-- time expressed as the number of milliseconds, 
-- due to ASN.1 limitation in OSS, the highest bit is set to 0

Psid ::= VarLengthNumber
--IpAddress ::= UTF8String(SIZE(2..255)) ---- text string containing IPv6 (or IPv4 or hostname). Used as a parameter in WSA, IPv6 configuration, etc
--IpPort ::= INTEGER(0..65535)      ---- UDP port used in WSA, in SetInitialState

RepeatRate ::= INTEGER (0..255) -- Number of messages transmitted per 5sec interval; if set to 0, transmit message one time only

MsgID ::=  INTEGER(0..255)


BandwidthPC5  ::= INTEGER (0..255)
TXpowerPC5    ::= INTEGER(-128..127)
EARFCN        ::= INTEGER(0..65535)
MCS           ::= INTEGER(0..64)
PSxCH  		  ::= ENUMERATED {
			pscch (1),
			pssch (2)
}
RBSize        ::= INTEGER(0..65535)
RBCount       ::= INTEGER(0..65535)
SPS           ::= INTEGER(0..65535)
PC5Event		::= INTEGER(0..65535)
PPPP          ::= INTEGER(0..65535)
PacketCount ::= INTEGER(0..9223372036854775807) 
PacketSize    ::= INTEGER(0..2040)
RSSI          ::= RCPI

/* 
-- Channel identifier and transit parameters
txPoolEarfcn ARFCN-ValueEUTRA-r9 OPTIONAL,
pMax P-Max OPTIONAL,
pppp SL-Priority-r13 OPTIONAL,
txPool SL-TxPoolIdentity-r12 OPTIONAL,
minMcs INTEGER (0..31) OPTIONAL, 
maxMcs INTEGER (0..31) OPTIONAL, 
minPdb INTEGER (0..1023) OPTIONAL, 
-- Traffic limiting 
mtu INTEGER (1..8192) OPTIONAL, 
maxBwPerSec MaxBandwidthPerSec OPTIONAL, 
minPeriodicity MinimumTrafficPeriodicity OPTIONAL, 
-- Operational parameters 
maxSpeed INTEGER (0..255) OPTIONAL, 
maxRange INTEGER (1..4096) OPTIONAL, 
maxCbr INTEGER (0..100) OPTIONAL, 
-- Preconfiguration 
preconfigInfo SL-V2X-Preconfiguration-r14 OPTIONAL, 
*/

END
